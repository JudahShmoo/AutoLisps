(defun c:rotate-to ( / pt1 pt2 pt3 pt4 basepoint fromdist todist selset ) 
	(setq pt1 (getpoint "\nSelect first point to rotate from: "))
	(print pt1)
	(setq pt2 (getpoint "\nSelect second point to rotate from: "))
	(print pt2)
	(setq pt3 (getpoint "\nSelect first point to rotate to: "))
	(print pt3)
	(setq pt4 (getpoint "\nSelect second point to rotate to: "))
	(print pt4)
	(setq basepoint (getpoint "\nSelect base point: "))
	(print basepoint)
	(setq fromangle (angle pt1 pt2))
	(setq fromangle-deg (/ (* fromangle 180.0) pi))
	(print (strcat "From angle: " (rtos fromangle-deg 2 4)))
	(setq toangle (angle pt3 pt4))
	(setq toangle-deg (/ (* toangle 180.0) pi))
	(print (strcat "To angle: " (rtos toangle-deg 2 4)))
	(command "ROTATE" (ssget) "" basepoint (- toangle-deg fromangle-deg))
)
