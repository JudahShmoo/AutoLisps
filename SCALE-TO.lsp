(defun c:scale-to ( / pt1 pt2 pt3 pt4 basepoint fromdist todist selset ) 
	(setq pt1 (getpoint "\nSelect first point of scale from: "))
	(print pt1)
	(setq pt2 (getpoint "\nSelect second point of scale from: "))
	(print pt2)
	(setq pt3 (getpoint "\nSelect first point of scale to: "))
	(print pt3)
	(setq pt4 (getpoint "\nSelect second point of scale to: "))
	(print pt4)
	(setq basepoint (getpoint "\nSelect base point: "))
	(print basepoint)
	(setq fromdist (distance pt1 pt2))
	(print (strcat "From distance: " (vl-princ-to-string fromdist)))
	(setq todist (distance pt3 pt4))
	(print (strcat "To distance: " (vl-princ-to-string todist)))
	(command "SCALE" (ssget) "" basepoint (/ todist fromdist))
)
